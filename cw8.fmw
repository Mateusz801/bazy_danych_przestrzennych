FME workspace cw8.fmw

Parameters:
- DestDataset_GEOJSON_3 = $(FME_MF_DIR)poi_path_length.json   # Destination GeoJSON File
- DestDataset_GEOJSON = $(FME_MF_DIR)poi_path_cost.json   # Destination GeoJSON File
- SourceDataset_GEOJSON = $(FME_MF_DIR)poi_path_cost.json   # Source GeoJSON File or URL
- DestDataset_GEODATABASE_FILE = LengthStatistics   # File Geodatabase
- SourceDataset_SHAPEFILE_6 = $(FME_MF_DIR)Dane\T2019_KAR_GERMANY\T2019_KAR_STREETS.shp   # Source Esri Shapefile(s)
- SourceDataset_CSV2_3 = $(FME_MF_DIR)Dane\routePoints.csv   # Source CSV (Comma Separated Value) File(s)
- SourceDataset_SHAPEFILE_7 = $(FME_MF_DIR)Dane\T2019_KAR_GERMANY\T2019_KAR_STREET_NODE.shp   # Source Esri Shapefile(s)
- SourceDataset_SHAPEFILE_5 = $(FME_MF_DIR)Dane\T2019_KAR_GERMANY\T2019_KAR_POI_TABLE.shp   # Source Esri Shapefile(s)

Readers:
- GEOJSON_3: GEOJSON from $(SourceDataset_GEOJSON)
- SHAPEFILE_4: SHAPEFILE from $(SourceDataset_SHAPEFILE_6) in LL-WGS84
- CSV2_2: CSV2 from $(SourceDataset_CSV2_3) in LL-WGS84
- SHAPEFILE_3: SHAPEFILE from $(SourceDataset_SHAPEFILE_7) in LL-WGS84
- SHAPEFILE_2: SHAPEFILE from $(SourceDataset_SHAPEFILE_5) in LL-WGS84

Writers:
- GEOJSON_2: GEOJSON to $(DestDataset_GEOJSON) in DHDN.Berlin/Cassini
- GEOJSON_1: GEOJSON to $(DestDataset_GEOJSON_3) in DHDN.Berlin/Cassini
- FILEGDB_1: FILEGDB to $(DestDataset_GEODATABASE_FILE)

T2019_KAR_STREETS (reader SHAPEFILE_4)
    attributes: LINK_ID long, ST_NAME varchar(254), REF_IN_ID long, NREF_IN_ID long, FUNC_CLASS varchar(1), SPEED_CAT varchar(1), FR_SPEED_L long, TO_SPEED_L long, DIR_TRAVEL varchar(1)
    -> Reprojector-zad4_4
Note: Reprojekcja
Reprojector-zad4_4
    DEST = DHDN.Berlin/Cassini
    INTERPOLATION_TYPE_NAME = Nearest Neighbor
    RASTER_CELL_SIZE = Preserve Cells
    RASTER_TOLERANCE = 0.0
    REPROJECTED -> ShortestPathFinder [NETWORK]
    REPROJECTED -> Tester
Note: Jednokierunkowa czy nie
Tester
    BOOL_OP = OR
    TEST_CLAUSE = TEST @Value(DIR_TRAVEL) = T
    TEST_MODE = TEST
    PASSED -> AttributeCreator
    FAILED -> AttributeCreator_2
AttributeCreator
    ATTR_TABLE:
      SET_TO ForwardCost = 1
      SET_TO ReverseCost = 9999
    -> ShortestPathFinder_2 [NETWORK]
AttributeCreator_2
    ATTR_TABLE:
      SET_TO ForwardCost = 1
      SET_TO ReverseCost = 1
    -> ShortestPathFinder_2 [NETWORK]
CSV (reader CSV2_2)
    attributes: x x_coordinate, y y_coordinate
    -> VertexCreator_zad3
Note: Tworzenie vertexów
VertexCreator_zad3
    MEASURE_TYPE = Continuous
    MODE_NAME = Replace with Point
    XVAL = @Value(x)
    YVAL = @Value(y)
    -> LineBuilder_zad3
Note: Linia
LineBuilder_zad3
    ACCUM_INPUT_ATTRS = Use Attributes From One Feature
    REMOVE_DUPLICATES = No
    LINE -> Reprojector-zad4
Note: Reprojekcja
Reprojector-zad4
    DEST = DHDN.Berlin/Cassini
    INTERPOLATION_TYPE_NAME = Nearest Neighbor
    RASTER_CELL_SIZE = Preserve Cells
    RASTER_TOLERANCE = 0.0
    REPROJECTED -> ShortestPathFinder [FROM-TO]
    REPROJECTED -> ShortestPathFinder_2 [FROM-TO]
Note: Najkrótsza droga bez uwzględniania kosztów
ShortestPathFinder
    ALLOW_UTURNS = Yes
    REORDER_MODE = NONE
    SNAP_POINTS = Yes
    SNAP_TOLERANCE = 200
    WEIGHT_ATTR_CHOICE = BY_LENGTH
    PATH -> Bufferer_2
    PATH -> SpatialRelator_zad7 [Supplier]
    PATH -> LengthPathLengthCalculator
Note: Długośc drogi
LengthPathLengthCalculator: LengthCalculator
    DIM = 2
    LEN_ATTR = _length
    MULT = 1
    -> LengthStatisticsCalculator
Note: Bufor 5m
Bufferer_2
    ANGLE = 22.5
    CAP_STYLE = Arc
    CORNER_STYLE = Arc
    MODE = AREA
    OFFSET = 5
    OFFSET_UNITS = METERS
    PRECISION = APPROX
    BUFFERED -> SpatialRelator_zad5 [Supplier]
Note: Droga z uwzględnieniem kosztów
ShortestPathFinder_2
    ALLOW_UTURNS = No
    REORDER_MODE = NONE
    SNAP_POINTS = Yes
    SNAP_TOLERANCE = 200
    WEIGHT_ATTR_1 = ForwardCost
    WEIGHT_ATTR_2 = ReverseCost
    WEIGHT_ATTR_CHOICE = BY_TWO_ATTRIBUTES
    PATH -> Bufferer
    PATH -> SpatialRelator_zad7_2 [Supplier]
    PATH -> CostPathLengthCalculator
CostPathLengthCalculator: LengthCalculator
    DIM = 2
    LEN_ATTR = _length
    MULT = 1
    -> CostStatisticsCalculator
Note: Bufor 5m
Bufferer
    ANGLE = 22.5
    CAP_STYLE = Arc
    CORNER_STYLE = Arc
    MODE = AREA
    OFFSET = 5
    OFFSET_UNITS = METERS
    PRECISION = APPROX
    BUFFERED -> SpatialRelator_zad5_2 [Supplier]
T2019_KAR_STREET_NODE (reader SHAPEFILE_3)
    attributes: NODE_ID long, LINK_ID long, POINT_NUM long, Z_LEVEL long, INTERSECT varchar(1), LAT number(31,15), LON number(31,15)
    -> Reprojector-zad4_3
Note: Reprojekcja
Reprojector-zad4_3
    DEST = DHDN.Berlin/Cassini
    INTERPOLATION_TYPE_NAME = Nearest Neighbor
    RASTER_CELL_SIZE = Preserve Cells
    RASTER_TOLERANCE = 0.0
    REPROJECTED -> Tester_zad7
Note: Czy punkt jest skrzyżowaniem
Tester_zad7
    BOOL_OP = OR
    TEST_CLAUSE = TEST @Value(INTERSECT) = Y
    TEST_MODE = TEST
    PASSED -> SpatialRelator_zad7_2 [Requestor]
    PASSED -> SpatialRelator_zad7 [Requestor]
Note: Skrzyżowania, które przecina wyznaczona droga
SpatialRelator_zad7
    AGGREGATE_HANDLING = Yes
    CALC_CARD = No
    CURVE_BOUNDARY_RULE_PARAM = Default Rule
    LIST_NAME = _relationships
    PREDICATES = INTERSECTS
    SUCCESS_ATTR = _related_suppliers
    -> intersectPathLengthTester
Note: Odfiltrowanie danych
intersectPathLengthTester: Tester
    BOOL_OP = OR
    TEST_CLAUSE = TEST @Value(_related_suppliers) = 1
    TEST_MODE = TEST
    PASSED -> LengthStatisticsCalculator
LengthStatisticsCalculator: StatisticsCalculator
    CALCULATION_MODE = NUMERIC
    FEAT_STATS = LAT,NUMERIC_MODE,,,,,,,,,,,,,;LINK_ID,NUMERIC_MODE,,,,,,,,VALUE_COUNT,,,,,;LON,NUMERIC_MODE,,,,,,,,,,,,,;NODE_ID,NUMERIC_MODE,,,,,,,,,,,,,;POINT_NUM,NUMERIC_MODE,,,,,,,,,,,,,;Z_LEVEL,NUMERIC_MODE,,,,,,,,,,,,,;_length,NUMERIC_MODE,,,,SUM,,,,,,,,,
    SUMMARY -> LengthStatistics (writer FILEGDB_1)
LengthStatistics (writer FILEGDB_1)
    attributes: LINK_ID_value_count double, _length_sum double
Note: Skrzyżowania, które przecina wyznaczona droga
SpatialRelator_zad7_2
    AGGREGATE_HANDLING = Yes
    CALC_CARD = No
    CURVE_BOUNDARY_RULE_PARAM = Default Rule
    LIST_NAME = _relationships
    PREDICATES = INTERSECTS
    SUCCESS_ATTR = _related_suppliers
    -> intersectPathCostTester_2
Note: Odfiltrowanie danych
intersectPathCostTester_2: Tester
    BOOL_OP = OR
    TEST_CLAUSE = TEST @Value(_related_suppliers) = 1
    TEST_MODE = TEST
    PASSED -> CostStatisticsCalculator
CostStatisticsCalculator: StatisticsCalculator
    CALCULATION_MODE = NUMERIC
    FEAT_STATS = LAT,NUMERIC_MODE,,,,,,,,,,,,,;LINK_ID,NUMERIC_MODE,,,,,,,,VALUE_COUNT,,,,,;LON,NUMERIC_MODE,,,,,,,,,,,,,;NODE_ID,NUMERIC_MODE,,,,,,,,,,,,,;POINT_NUM,NUMERIC_MODE,,,,,,,,,,,,,;Z_LEVEL,NUMERIC_MODE,,,,,,,,,,,,,;_length,NUMERIC_MODE,,,,SUM,,,,,,,,,
    SUMMARY -> CostStatistics (writer FILEGDB_1)
CostStatistics (writer FILEGDB_1)
    attributes: LINK_ID_value_count double, _length_sum double
T2019_KAR_POI_TABLE (reader SHAPEFILE_2)
    attributes: POI_ID long, LINK_ID long, TYPE varchar(250), POI_NAME varchar(250), ST_NAME varchar(250), LAT number(31,15), LON number(31,15)
    -> Reprojector-zad4_2
Note: Reprojekcja
Reprojector-zad4_2
    DEST = DHDN.Berlin/Cassini
    INTERPOLATION_TYPE_NAME = Nearest Neighbor
    RASTER_CELL_SIZE = Preserve Cells
    RASTER_TOLERANCE = 0.0
    REPROJECTED -> SpatialRelator_zad5_2 [Requestor]
    REPROJECTED -> SpatialRelator_zad5 [Requestor]
Note: POI w zasięgu bufora
SpatialRelator_zad5
    AGGREGATE_HANDLING = Yes
    CALC_CARD = No
    CURVE_BOUNDARY_RULE_PARAM = Default Rule
    LIST_NAME = _relationships
    PREDICATES = WITHIN
    SUCCESS_ATTR = _related_suppliers
    -> poiPathLengthTester
Note: Odfiltrowanie danych
poiPathLengthTester: Tester
    BOOL_OP = OR
    TEST_CLAUSE = TEST @Value(_related_suppliers) = 1
    TEST_MODE = TEST
    PASSED -> poi_in_length (writer GEOJSON_1)
poi_in_length (writer GEOJSON_1)
    attributes: POI_ID int, LINK_ID int, TYPE string, POI_NAME string, ST_NAME string, LAT float, LON float, _relationships{}.x float, _relationships{}.y float, _relationships{}._total_cost string, _relationships{}.de9im string, _relationships{}.pass{} string, _related_suppliers int
Note: POI w zasięgu bufora
SpatialRelator_zad5_2
    AGGREGATE_HANDLING = Yes
    CALC_CARD = No
    CURVE_BOUNDARY_RULE_PARAM = Default Rule
    LIST_NAME = _relationships
    PREDICATES = WITHIN
    SUCCESS_ATTR = _related_suppliers
    -> poiPathCostTester
Note: Odfiltrowanie danych
poiPathCostTester: Tester
    BOOL_OP = OR
    TEST_CLAUSE = TEST @Value(_related_suppliers) = 1
    TEST_MODE = TEST
    PASSED -> poi_in_cost (writer GEOJSON_2)
poi_in_cost (writer GEOJSON_2)
    attributes: POI_ID int, LINK_ID int, TYPE string, POI_NAME string, ST_NAME string, LAT float, LON float, _relationships{}.x float, _relationships{}.y float, _relationships{}._total_cost string, _relationships{}.de9im string, _relationships{}.pass{} string, _related_suppliers int
